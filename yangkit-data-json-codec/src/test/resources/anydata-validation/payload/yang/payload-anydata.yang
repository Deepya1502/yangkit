module payload-anydata {
  yang-version 1.1;
  namespace "urn:test:payload-anydata";
  prefix payload;

  container payload-root {
    leaf value {
      type string;
    }

    list item {
      key "id";
      unique "details/name";

      leaf id {
        type string;
      }
      container details {
        leaf name {
          type string;
        }
      }
    }
  }
}
