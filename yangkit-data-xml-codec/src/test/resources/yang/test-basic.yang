module test-basic {
    namespace "urn:test:basic";
    prefix tb;
    
    container config {
        leaf name {
            type string;
        }
        leaf enabled {
            type boolean;
        }
        list server {
            key "id";

            leaf id {
                type string;
            }
            leaf description {
                type string;
            }
            container settings {
                leaf mode {
                    type string;
                }
            }
        }
    }
}
